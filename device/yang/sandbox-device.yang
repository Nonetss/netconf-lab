module sandbox-device {
  yang-version 1.1;
  namespace "urn:sandbox:device";
  prefix sd;
  organization
    "NETCONF Sandbox";
  description
    "A compact device model for NETCONF/YANG laboratory exercises.";
  revision 2026-09-12 {
    description
      "Initial sandbox revision.";
  }

  typedef severity {
    type enumeration {
      enum info;
      enum warning;
      enum critical;
    }
  }

  container system {
    presence
      "Enables the simulated system configuration.";
    description
      "Configurable system identity and live system state.";
    leaf hostname {
      type string {
        length "1..63";
      }
      mandatory true;
    }
    leaf location {
      type string;
    }
    leaf contact {
      type string;
    }
    container state {
      config false;
      leaf vendor {
        type string;
        mandatory true;
      }
      leaf model {
        type string;
        mandatory true;
      }
      leaf serial-number {
        type string;
        mandatory true;
      }
      leaf software-version {
        type string;
        mandatory true;
      }
      leaf boot-time {
        type string;
        mandatory true;
      }
      leaf uptime-seconds {
        type uint64;
        mandatory true;
      }
      leaf cpu-percent {
        type decimal64 {
          fraction-digits 1;
          range "0..100";
        }
        mandatory true;
      }
      leaf memory-used-percent {
        type decimal64 {
          fraction-digits 1;
          range "0..100";
        }
        mandatory true;
      }
    }
  }

  container inventory {
    config false;
    list component {
      key "name";
      leaf name {
        type string;
      }
      leaf class {
        type enumeration {
          enum chassis;
          enum module;
          enum port;
          enum fan;
          enum power-supply;
        }
        mandatory true;
      }
      leaf serial-number {
        type string;
      }
      leaf description {
        type string;
      }
      leaf oper-status {
        type enumeration {
          enum up;
          enum down;
          enum degraded;
          enum unknown;
        }
        mandatory true;
      }
    }
  }

  rpc ping {
    input {
      leaf destination {
        type string;
        mandatory true;
      }
      leaf count {
        type uint8 {
          range "1..5";
        }
        default 3;
      }
    }
    output {
      leaf success {
        type boolean;
        mandatory true;
      }
      leaf packets-sent {
        type uint8;
        mandatory true;
      }
      leaf packets-received {
        type uint8;
        mandatory true;
      }
      leaf message {
        type string;
      }
    }
  }

  rpc reboot {
    description
      "Simulate a device reboot by resetting boot time and counters.";
    input {
      leaf delay-seconds {
        type uint16 {
          range "0..300";
        }
        default 0;
      }
    }
    output {
      leaf accepted {
        type boolean;
        mandatory true;
      }
      leaf message {
        type string;
        mandatory true;
      }
    }
  }

  notification alarm {
    leaf severity {
      type severity;
      mandatory true;
    }
    leaf resource {
      type string;
      mandatory true;
    }
    leaf text {
      type string;
      mandatory true;
    }
  }
}
